Aloof-Protocol
DEFINITIONS 
::=

BEGIN

    Message ::= CHOICE
    {
        hello       [0] Hello,
        hello-hello [1] Hello,
        
        error       [2] Error,
        
        command     [3] Command,
        response    [4] Response,
        alert       [5] Alert  
    }

    Hello ::= SEQUENCE 
    {
        station ENUMERATED 
        {  
            client (0),
            server (1)
        },
        
        version Uint,        
        
        features BIT STRING SIZE(32)
    }
    
    Error ::= NULL
    
    Command ::= SEQUENCE
    {
        invocation-field Invocation-Field,
        
        command-type CHOICE 
        {
            write-object    [0] Write-Object-Command,
            read-object     [1] Read-Object-Command,
            write-file      [2] Write-File-Command,
            read-file       [3] Read-File-Command
        }
    }
    
    Response ::= SEQUENCE
    {
        invocation-field Invocation-Field,
        
        response-type CHOICE 
        {
            write-object    [0] Write-Object-Response,
            read-object     [1] Read-Object-Response,
            write-file      [2] Write-File-Response,
            read-file       [3] Read-File-Response
        }    
    }

    Invocation-Field ::= BIT STRING SIZE(8)
    {
        confirm         (0),
        invoke-id-6     (1),
        invoke-id-5     (2),
        invoke-id-4     (3),
        invoke-id-3     (4),
        invoke-id-2     (5),
        invoke-id-1     (6),
        invoke-id-0     (7)
    }

    Alert ::= SEQUENCE
    {
        alert-id    Uint,
        data        SEQUENCE SIZE(0..max-u32) OF Data
    }

    Write-Object-Command ::= SEQUENCE
    {
        oid     Uint,
        data    Data
    }

    Write-Object-Response ::= CHOICE
    {
        success [0] NULL,
        failure [1] Access-Error
    }

    Read-Object-Command ::= SEQUENCE
    {
        oid     Uint,
        data    Data
    }

    Read-Object-Response ::= CHOICE
    {
        success [0] Data,
        failure [1] Access-Error
    }

    Write-File-Command ::= SEQUENCE
    {
        oid     Uint,
        offset  Uint,
        data    OCTET STRING (SIZE(0..max-u32))
    }

    Write-File-Response ::= CHOICE
    {
        success [0] SEQUENCE 
        {
            bytes-written Uint        
        },
        failure [1] Access-Error        
    }
    
    Read-File-Command ::= SEQUENCE
    {
        oid     Uint,
        offset  Uint,
        bytes   Uint        
    }

    Read-File-Response ::= CHOICE
    {
        success [0] SEQUENCE 
        {
            data OCTET STRING (SIZE(0..max-u32))
        },
        failure [1] Access-Error        
    }

    Data ::= CHOICE
    {
        nil     [0] NULL,
        
        u8      [1] U8,
        u16     [2] U16,
        u32     [3] U32,
        u64     [4] U64,
        
        i8      [5] I8,
        i16     [6] I16,
        i32     [7] I32,
        i64     [8] I64,
        
        bool    [9] BOOLEAN,
        
        float   [10] Single-Float,
        double  [11] Double-Float,
        
        string  [12] OCTET STRING (SIZE(0..max-u32)),
        blob    [13] OCTET STRING (SIZE(0..max-u32))
    }
    
    Access-Error ::= ENUMERATED
    {
        unknown,
        access,
        authentication,
        type,
        argument,
        temporary,
        application
    }
    
    Uint ::= INTEGER (0..MAX)

    U8 ::= INTEGER (0..255)
    U16 ::= INTEGER (0..65535)
    U32 ::= INTEGER (0..4294967295)
    U64 ::= INTEGER (0..18446744073709551615)

    Single-Float ::= REAL
    Double-Float ::= REAL
    
    I8 ::= INTEGER (-128..127)
    I16 ::= INTEGER (-32768..32767)
    I32 ::= INTEGER (-2147483648..2147483647)
    I64 ::= INTEGER (-9223372036854775808..9223372036854775807)

    max-u32 INTEGER ::= 4294967295

END
